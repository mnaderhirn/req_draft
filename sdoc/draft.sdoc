[DOCUMENT]
TITLE: StrictDoc

[REQUIREMENT]
UID: REQ-001
REFS:
- TYPE: File
  VALUE: draft.py
- TYPE: File
  VALUE: draft.c
- TYPE: File
  VALUE: draft.cpp
- TYPE: File
  VALUE: draft.tex
- TYPE: File
  VALUE: fha.fods

[REQUIREMENT]
UID: REQ-002
REFS:
- TYPE: Parent
  VALUE: REQ-001
- TYPE: File
  VALUE: draft.py
- TYPE: File
  VALUE: fha.fods
